from pivy_trackers.core.examples.select_drag.select_drag_tracker import SelectDragTracker
tracker = SelectDragTracker(Gui.ActiveDocument.ActiveView, is_linked=True, has_markers=False)
tracker.insert_into_scenegraph(True)
